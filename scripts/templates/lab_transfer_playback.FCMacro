"""Source-derived L01 roundtrip, evaluated from canonical C2 PVA curves."""
import json
import math
import time
import hashlib
import sys
from pathlib import Path
import FreeCAD as App
import FreeCADGui as Gui
from PySide import QtCore, QtWidgets

document_path=__DOCUMENT__
sys.path.insert(0,__ROOT__+'/scripts')
import lab_transfer_motion as model
timeline_path=Path(__TIMELINE_PATH__)
if hashlib.sha256(timeline_path.read_bytes()).hexdigest()!=__TIMELINE_SHA256__:raise ValueError('L01 timeline artifact changed')
timeline=json.loads(timeline_path.read_text());spec=model.load();spatial=model.layout.load(validate_builds=False)
model.verify_sources(timeline,spec,spatial)
evaluate=model.Evaluator(timeline,spec,spatial)
doc=next((d for d in App.listDocuments().values() if d.FileName==document_path),None) or App.openDocument(document_path)
App.setActiveDocument(doc.Name)
duration=timeline['duration_s']

class TransferPlayer(QtWidgets.QWidget):
    def __init__(self):
        super().__init__();self.setWindowTitle('L01 sample roundtrip — simulation')
        self.t=0.;self.playing=False;self.last=time.monotonic();self.rate=4.
        box=QtWidgets.QVBoxLayout(self);self.button=QtWidgets.QPushButton('Play / pause');box.addWidget(self.button)
        self.button.clicked.connect(self.toggle)
        self.slider=QtWidgets.QSlider(QtCore.Qt.Horizontal);self.slider.setRange(0,round(duration*1000));box.addWidget(self.slider)
        self.slider.valueChanged.connect(self.seek);self.label=QtWidgets.QLabel();box.addWidget(self.label)
        box.addWidget(QtWidgets.QLabel('4× playback · rotor stopped · assumed handling tool'))
        self.timer=QtCore.QTimer(self);self.timer.timeout.connect(self.tick);self.timer.start(40);self.apply()
    def toggle(self):self.playing=not self.playing;self.last=time.monotonic()
    def seek(self,v):self.t=v/1000;self.apply()
    def tick(self):
        now=time.monotonic();dt=now-self.last;self.last=now
        if not self.playing:return
        self.t=min(duration,self.t+dt*self.rate)
        if self.t>=duration:self.playing=False
        self.slider.blockSignals(True);self.slider.setValue(round(self.t*1000));self.slider.blockSignals(False);self.apply()
    def apply(self):
        frame=evaluate(self.t)
        for i in range(6):setattr(doc.ArmCControl,'J'+str(i+1),frame['q'][i])
        for name,value in frame['cf'].items():setattr(doc.CF01Control,name,value)
        bottom=frame['sample_bottom'];axis=frame['sample_axis']
        doc.Sample.Placement=App.Placement(App.Vector(*bottom),App.Rotation(App.Vector(0,0,1),App.Vector(*axis)))
        doc.recompute();Gui.activeDocument().activeView().redraw()
        self.label.setText('%5.1f / %.1f s — %s'%(self.t,duration,frame['phase']))
    def closeEvent(self,event):self.timer.stop();super().closeEvent(event)

_l01_transfer_player=TransferPlayer();_l01_transfer_player.resize(620,180);_l01_transfer_player.show()
Gui.activeDocument().activeView().viewAxonometric();Gui.activeDocument().activeView().fitAll()
